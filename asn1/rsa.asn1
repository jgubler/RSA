RsaKeys DEFINITIONS ::= BEGIN

PubKey ::= SEQUENCE {
	modulus			INTEGER,
	publicExponent 	INTEGER

}

PrKey ::= SEQUENCE {
	modulus			INTEGER,
	publicExponent	INTEGER,
	privateExponent	INTEGER,
	prime1			INTEGER,
	prime2			INTEGER,
	exponent1		INTEGER,
	exponent2		INTEGER,
	coefficient		INTEGER
}

END
